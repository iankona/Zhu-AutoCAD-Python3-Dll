(defun zhu_load_plugin()
(command "netload" "E:\\CADdll\\CADpythondll.dll")
(command "zhu_hello")
(command "netload" "E:\\CADdll\\ZhuAcadPlugin.dll")
(command "zhu_world")
(princ)
)

(zhu_load_plugin)
(princ)

;(defun c:LoadMyPlugin ()
;    (vl-load-com)
;    (setq acadObj (vlax-get-acad-object))
;    (setq acadDoc (vla-get-ActiveDocument acadObj))
;    (setq acadApp (vlax-get-or-create-object "AutoCAD.Application"))
;    (setq acadDoc (vla-get-ActiveDocument acadApp))
;    (setq acadMod (vla-get-Application acadDoc))
;    (vla-Load (vla-GetInterfaceObject acadMod "MyPlugin.dll"))
;)

;(princ "\nLoading MyPlugin.dll...")
;(c:LoadMyPlugin)
;(princ)
